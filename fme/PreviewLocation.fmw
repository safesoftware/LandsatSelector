FME workspace PreviewLocation.fmw

Parameters:
- LONGITUDE = -123   # Longitude
- LATITUDE = 49.2   # Latitude
- PREVIEWURL = https://landsat-pds.s3.amazonaws.com/L8/047/026/LC80470262016232LGN00/LC80470262016232LGN00_thumb_small.jpg   # Preview URL
- X_UL_COORD = 397500   # X Upper Left Coordinate
- Y_UL_COORD = 5531700   # Y Upper Left Coordinate
- X_UR_COORD = 633600   # X Upper Right Coordinate
- Y_UR_COORD = 5531700   # Y Upper Right Coordinate
- X_LR_COORD = 633600   # X Lower Right Coordinate
- Y_LR_COORD = 5292600   # Y Lower Right Coordinate
- X_LL_COORD = 397500   # X Lower Left Coordinate
- Y_LL_COORD = 5292600   # Y Lower Left Coordinate
- UTMZONE = 10   # UTM Zone
- LY_LL = 47.77291   # Lower Y in LL
- PROJECTION = UTM   # Projection

Writers:
- JPEG_1: JPEG to $(FME_MF_DIR)images

Note: Overlay the ring over the preview
VectorOnRasterOverlayer
    ALPHA = 1.0
    ANTI_ALIASING = Yes
    COMPOSITE_USING_ALPHA_BAND = No
    GROUP_BY = _rootname
    RASTER -> aaa (writer JPEG_1)
Note: Save the image (or stream back on server
aaa (writer JPEG_1)

Bookmark: Get path to image and coordinates, get the image and georeference it
Creator
    GEOMTYPE = Geometry Object
    NUM = 1
    CREATED -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(PREVIEWURL)
    -> ImageFetcher
ImageFetcher
    CONNECTION_TIMEOUT_LENGTH = 60
    ERROR_ATTR = _http_error
    FOLLOW_REDIRECTS = Yes
    RASTER_TYPE = JPEG
    RESPONSE_HEADER_LIST_ATTR = _http_headers
    STATUS_CODE_ATTR = _http_status_code
    TRANSFER_TIMEOUT_LENGTH = 90
    URL = $(PREVIEWURL)
    USE_COOKIES = No
    VERIFY_SSL_CERTIFICATES = Yes
    RASTER -> RasterGeoreferencer
RasterGeoreferencer
    POINTANDANGLE_OR_EXTENTS = Extents
    X_LL_COORD = $(X_LL_COORD)
    X_LR_COORD = $(X_LR_COORD)
    X_UL_COORD = $(X_UL_COORD)
    X_UR_COORD = $(X_UR_COORD)
    Y_LL_COORD = $(Y_LL_COORD)
    Y_LR_COORD = $(Y_LR_COORD)
    Y_UL_COORD = $(Y_UL_COORD)
    Y_UR_COORD = $(Y_UR_COORD)
    -> AttributeCreator_3
    -> VectorOnRasterOverlayer [RASTER]

Bookmark: Make a ring around the location where the map was clicked
AttributeCreator_3
    ATTR_TABLE = SET_TO _cs = FME_CONDITIONAL:DEFAULT_VALUE'UTM84-$(UTMZONE)S'BOOL_OP;AND;COMPOSITE_TEST;<Unused>;TEST $(PROJECTION) = PS;TEST $(LATITUDE) <= -80'WGS84.AArcticPStero_FME'BOOL_OP;AND;COMPOSITE_TEST;<Unused>;TEST $(PROJECTION) = PS;TEST $(LATITUDE) >= 84'WGS84.ArcticPStero_FME'BOOL_OP;OR;COMPOSITE_TEST;<Unused>;TEST $(LY_LL) > -8'UTM84-$(UTMZONE)N'FME_NUM_CONDITIONS4___
    -> VertexCreator_2
VertexCreator_2
    MEASURE_TYPE = Continuous
    MODE_NAME = Replace with Point
    XVAL = $(LONGITUDE)
    YVAL = $(LATITUDE)
    -> CoordinateSystemRemover
CoordinateSystemRemover
    -> Reprojector
Reprojector
    DEST = @Value(_cs)
    INTERPOLATION_TYPE_NAME = Nearest Neighbor
    RASTER_CELL_SIZE = Preserve Cells
    RASTER_TOLERANCE = 0.0
    SOURCE = LL84
    REPROJECTED -> FeatureColorSetter
FeatureColorSetter
    COLOR = 1,0.247059,0.247059
    FILL_COLOR = 1,0.498039,0.498039
    MODE = Fixed
    COLORED -> CoordinateExtractor
CoordinateExtractor
    IND = 0
    MODE = Specify Coordinate
    X_ATTR = _x
    Y_ATTR = _y
    Z_ATTR = _z
    -> 2DEllipseReplacer
    -> 2DEllipseReplacer_2
2DEllipseReplacer_2
    PRIMAXIS = 4000
    ROT = 0
    SECAXIS = 4000
    XVALATTR = @Value(_x)
    YVALATTR = @Value(_y)
    ELLIPSE -> DonutBuilder
2DEllipseReplacer
    PRIMAXIS = 5000
    ROT = 0
    SECAXIS = 5000
    XVALATTR = @Value(_x)
    YVALATTR = @Value(_y)
    ELLIPSE -> DonutBuilder
DonutBuilder
    CONNECT_Z_MODE = First Wins
    DROP = yes
    GROUP_BY = _rootname
    AREA -> VectorOnRasterOverlayer [VECTOR]
