FME workspace LandsatFileSelectorWithLocation.fmw
Title: LandsatFileSelector

Parameters:
- LONGITUDE = -69   # Longitude
- LATITUDE = -84   # Latitude
- CLOUDPERCENTAGE = 5   # Include only images with cloud coverage less or equal, %
- SourceDataset_SHAPEFILE = /Users/sanae.mendoza/Documents/demos/landsat/WRS2_descending_0/WRS2_descending.shp   # Source Esri Shapefile(s)

Readers:
- SHAPEFILE_1: SHAPEFILE from $(SourceDataset_SHAPEFILE)

Writers:
- HTML_1: HTML to $(FME_MF_DIR)c/temp/landsatSelector.html

Creator
    GEOMTYPE = Geometry Object
    NUM = 1
    CREATED -> ParameterFetcher
ParameterFetcher
    ATTR_LIST = _latitude $(LATITUDE) _longitude $(LONGITUDE)
    -> AttributeCreator_11
Note: Check for images
FeatureDetector
    NoInput -> AttributeCreator_3
    -> Sorter
Note: On Server streamback HTML page
HTML (writer HTML_1)
    attributes: html_content buffer

Bookmark: Compare selected position to tiles
AttributeCreator_11
    ATTR_TABLE:
      SET_TO _latitude = FME_CONDITIONAL:DEFAULT_VALUE'@Value(_latitude)'BOOL_OP;OR;COMPOSITE_TEST;<Unused>;TEST @Value(_latitude) > 80'80'BOOL_OP;OR;COMPOSITE_TEST;<Unused>;TEST @Value(_latitude) < -80'-80'FME_NUM_CONDITIONS3___
      SET_TO _longitude = FME_CONDITIONAL:DEFAULT_VALUE'@Value(_longitude)'BOOL_OP;OR;COMPOSITE_TEST;<Unused>;TEST @Value(_longitude) > 180'@Evaluate(@Value(_longitude)-360)'BOOL_OP;OR;COMPOSITE_TEST;<Unused>;TEST @Value(_longitude) < -180'@Evaluate(@Value(_longitude)+360)'FME_NUM_CONDITIONS3___
    -> VertexCreator
    -> FeatureDetector
VertexCreator
    MEASURE_TYPE = Continuous
    MODE_NAME = Replace with Point
    XVAL = @Value(_longitude)
    YVAL = @Value(_latitude)
    -> PointOnAreaOverlayer [POINT]
WRS2_descending (reader SHAPEFILE_1)
    attributes: AREA double, PERIMETER double, PR_ double, PR_ID double, RINGS_OK long, RINGS_NOK long, PATH long, ROW long, MODE char(1), SEQUENCE long, WRSPR char(50), PR char(50), ACQDayL7 char(50), ACQDayL8 char(50)
    -> PointOnAreaOverlayer [AREA]
Note: Find the Landsat tile / covering the supplied point
PointOnAreaOverlayer
    ATTR_ACCUM_MODE = Merge Incoming
    ATTR_CONFLICT_RES = Use Original
    DEAGGREGATE_INPUT = Yes
    LIST_NAME = list
    OV_ATTR = _overlaps
    POLYS_FIRST = NO
    POINT -> ListExploder
Note: If there are many tiles overlapping the point, / make a separate feature for each
ListExploder
    ATTR_ACCUM_MODE = Merge List Attributes
    ATTR_CONFLICT_RES = Use List Attribute Values
    INDEX_ATTR = _element_index
    LIST_ATTR = list{}
    ELEMENTS -> StringFormatter

Bookmark: Prepare folder name for S3 storage
StringFormatter
    FORMAT = 03d
    SRC_ATTRS = ROW,PATH
    -> AttributeCreator
AttributeCreator
    ATTR_TABLE = SET_TO _landsat_tile_url = L8/@Value(PATH)/@Value(ROW)/
    -> S3Connector
    -> AttributeRemover_2

Bookmark: Get relevant images from S3 Bucket
Note: retrieve all objects for the point
S3Connector
    CREDENTIAL_SOURCE = Anonymous
    OPERATION_TYPE = List
    PARAMETER_SETUP = _FME_BUCKET]landsat-pds]_FME_FILES]@Value(_landsat_tile_url)]_FME_INCLUDE_SUBFOLDERS]Yes]_FME_OBJECT_NAME_ATTRIBUTE]_name]_FME_OBJECT_PATH_ATTRIBUTE]_s3_object_key]_FME_OBJECT_URL_ATTRIBUTE]_url]_FME_OBJECT_ID_ATTRIBUTE]_bucket_name]_FME_OBJECT_TYPE_ATTRIBUTE]_file_or_folder]_FME_OBJECT_SIZE_ATTRIBUTE]_file_size]_FME_OBJECT_MODIFIED_ATTRIBUTE]_file_last_modified]_FME_OBJECT_RELATIVE_PATH_ATTRIBUTE]_relative_path]FME_CONTROLLER_QUERY_FILE]amazons3_deps/List.fme
    _FME_S3_AWS_REGION = us-west-2
    _FME_S3_VERIFY_SSL = yes
    -> FeatureMerger_2 [REQUESTOR]
AttributeRemover_2
    REMOVE_ATTRS = ROW,PR_,RINGS_NOK,PERIMETER,DAYCLASS,SEQUENCE,_creation_instance,PR,WRSPR,PR_ID,_element_index,_overlaps,MODE,AREA,PATH,_landsat_tile_url,RINGS_OK
    -> Sampler
Sampler
    RATE = 1
    SAMPLE_MODE = No
    SAMPLE_TYPE_LONG = First N Features
    SAMPLED -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> SubstringExtractor
Note: Extract the date (yyyddd) from the name
SubstringExtractor
    END = 48
    RESULT_ATTR = _image_date
    SRC_STRING = @Value(_s3_object_key)
    START = 42
    -> DateFormatter
Note: Change the date format from yyyyddd to yyyy-mm-dd
DateFormatter
    DATE_ATTR = _image_date
    FMT = %Y-%m-%d
    INVALID_DATE_VALUE = _FME_NO_OP_
    SRCFMT = %Y%j
    -> SubstringExtractor_2
Note: take only the folder name
SubstringExtractor_2
    END = 31
    RESULT_ATTR = image_folder
    SRC_STRING = @Value(_s3_object_key)
    START = 0
    -> TestFilter
Note: Keep only previews and json metadata objects
TestFilter
    DEFAULT_VALUE = <UNFILTERED>
    TEST_LIST = BOOL_OP,AND,COMPOSITE_TEST,<Unused>,TEST_CLAUSE,"TEST @Value(_s3_object_key) CONTAINS json",JSON
    JSON -> HTTPCaller

Bookmark: Get cloud coverage, sun angle, and sun azimuth from metadata
HTTPCaller
    CONNECTION_TIMEOUT_LENGTH = 60
    ERROR_ATTR = _error
    FOLLOW_REDIRECTS = FOLLOW_WITH_ORIGINAL_METHOD
    HTTP_METHOD = GET
    REDIRECT_AUTH = ORIGINAL_DOMAIN_ONLY
    RESPONSE_HEADER_LIST_ATTR = _headers
    SAVE_FILE = Attribute
    STATUS_CODE_ATTR = _http_status_code
    TARGET_ATTR = _json
    TARGET_ATTR_ENCODING = auto-detect
    TARGET_URL = https://landsat-pds.s3.amazonaws.com/@Value(_s3_object_key)
    TRANSFER_TIMEOUT_LENGTH = 90
    USE_COOKIES = No
    VERIFY_SSL_CERTIFICATES = Yes
    -> JSONExtractor
JSONExtractor
    EXTRACT_QUERY_TABLE = cloud_coverage json[*][*]["CLOUD_COVER"] sun_angle json[*][*]["SUN_AZIMUTH"] sun_azimuth json[*][*]["SUN_ELEVATION"] x_ll_utm json[*][*]["CORNER_LL_PROJECTION_X_PRODUCT"] x_lr_utm json[*][*]["CORNER_LR_PROJECTION_X_PRODUCT"] x_ul_utm json[*][*]["CORNER_UL_PROJECTION_X_PRODUCT"] x_ur_utm json[*][*]["CORNER_UR_PROJECTION_X_PRODUCT"] y_ll_utm json[*][*]["CORNER_LL_PROJECTION_Y_PRODUCT"] y_lr_utm json[*][*]["CORNER_LR_PROJECTION_Y_PRODUCT"] y_ul_utm json[*][*]["CORNER_UL_PROJECTION_Y_PRODUCT"] y_ur_utm json[*][*]["CORNER_UR_PROJECTION_Y_PRODUCT"] utm_zone json[*][*]["UTM_ZONE"] y_ll json[*][*]["CORNER_LR_LAT_PRODUCT"] projection json[*][*]["MAP_PROJECTION"]
    JSON_DOCUMENT = @Value(_json)
    READ_FROM_FILE = NO
    EVALUATED -> Tester
Note: Apply cloud filter
Tester
    BOOL_OP = OR
    COMPOSITE_TEST = 1
    TEST_CLAUSE = TEST @Value(cloud_coverage) <= $(CLOUDPERCENTAGE)
    TEST_MODE = TEST
    PASSED -> AttributeCreator_9

Bookmark: HTML paths
Note: Build a path to preview
AttributeCreator_9
    ATTR_TABLE = SET_TO _preview = @ReplaceString(@Value(_s3_object_key),_MTL.json,_thumb_small.jpg)
    -> AttributeCreator_8
Note: Build HTML for each date
AttributeCreator_8
    ATTR_TABLE:
      SET_TO html_content = <a href="https://landsat-pds.s3.amazonaws.com/@ReplaceString(@Value(_preview),small,large)" target="_blank"><img src="https://demos-safe-software.fmecloud.com/fmedatastreaming/Landsat8Demo/PreviewLocation.fmw?LONGITUDE=@Value(_longitude)&LATITUDE=@Value(_latitude)&PREVIEWURL=https://landsat-pds.s3.amazonaws.com/@Value(_preview)&X_UL_COORD=@Value(x_ul_utm)&Y_UL_COORD=@Value(y_ul_utm)&X_UR_COORD=@Value(x_ur_utm)&Y_UR_COORD=@Value(y_ur_utm)&X_LR_COORD=@Value(x_lr_utm)&Y_LR_COORD=@Value(y_lr_utm)&X_LL_COORD=@Value(x_ll_utm)&Y_LL_COORD=@Value(y_ll_utm)&UTMZONE=@Value(utm_zone)&LY_LL=@Value(y_ll)&PROJECTION=@Value(projection)" alt="@Value(_s3_object_key)" width="343" height="343"></a>
      SET_TO data_coverage = 100
      SET_TO provider = Landsat
      SET_TO image_folder = https://landsat-pds.s3.amazonaws.com/@Value(image_folder)/index.html
    -> FeatureDetector

Bookmark: Format HTML Results Page
Note: No results page
AttributeCreator_3
    ATTR_TABLE:
      SET_TO html_content = <html>
         <head>
         </head>
         <body>
          <h1>No images meeting search criteria found</h1>
          <p>Return <a href="javascript:history.back();">back</a> and adjust your criteria by increasing allowed cloud coverage.</p>
          </body>
        </html>
    -> HTML (writer HTML_1)
    -> AttributeFileWriter [off]
Note: Sort images by date
Sorter
    SORT_PARM = _image_date ALPHA DESCENDING
    SORTED -> Counter
Note: Count how many images are on the page
Counter
    CNT_ATTR = _count
    DOMAIN = counter
    SCOPE = Global
    START = 1
    -> AttributeCreator_2
Note: Build HTML for each date
AttributeCreator_2
    ATTR_TABLE:
      SET_TO html_content =         <tr>
                  <td>@Value(_count)</td>
                  <td><input type="radio" name="preview" value="@Value(image_folder)"</td>
                  <td>@Value(provider)</td>
                  <td>@Value(html_content)</td>
                  <td>@Value(_image_date)</td>
                  <td align="center">@Value(cloud_coverage)</td>
                </tr>
    -> Aggregator
Note: Make a single HTML code for all entries
Aggregator
    ACCUM_ATTRS_NAME = Drop Incoming Attributes
    CONCAT_ATTRS = html_content
    MODE = Attributes Only
    SEP = "\n"
    AGGREGATE -> AttributeCreator_4
Note: Create full HTML page
AttributeCreator_4
    ATTR_TABLE:
      SET_TO html_content = <html>
         <head>
          <script>
            function OpenAmazonFolder(){
              var selectedImage = document.ImageSelector.preview.value;
              window.open(selectedImage, "_self")
            }
          </script>
          </head>
          <body>
            <h1>Select the image and press the button to open the download folder</h1>
            <form name="ImageSelector" >
               <br>
              <input type="button" value="Open Amazon S3 folder with selected images" onclick="OpenAmazonFolder()" >
              <br>
              <br>
              <table border="1">
                <tr>
                  <th>&nbsp;#&nbsp;</th>
                  <th>Select</th>
                  <th>Provider</th>
                  <th>Preview</th>
                  <th>Date</th>
                  <th>Cloud Coverage, %</th>

        @Value(html_content)
              </table>
            </form>
          </body>
               <style>
                body { font-family: sans-serif;}
                table, td, th { border : 1px solid black; }
                table {border-collapse: collapse;}
                th { padding : 10px; }
                td { padding : 7px; }
            </style>
        </html>
    -> AttributeFileWriter [off]
    -> HTML (writer HTML_1)

Bookmark: For Desktop
Note: Save HTML as a file
AttributeFileWriter
    CHAR_ENCODING = fme-system
    FILE_NAME = c:\temp\landsat.html
    OVERWRITE_FILE = Overwrite file
    SOURCE_ATTR = html_content
    -> SystemCaller
Note: Open HTML in browser
SystemCaller
    CMD = explorer c:\temp\landsat.html
    -> SystemCaller_Output
SystemCaller_Output: Logger
    LOG_FEATURE = LOG_RECORD
    MAXCOORDS = 0
    MAXFEATS = 0
    MESSAGE = Feature is:
    SEVERITY = INFO

FME custom transformer FeatureDetector
Outputs a single feature through NoInput port if there are no input features, or outputs all input features through Output port.

Input (input)
    -> Counter
Note: If only one feature, output through Passed / otherwise through failed
Tester
    BOOL_OP = OR
    TEST_CLAUSE = TEST @Value(_num_count) = 1
    TEST_MODE = Automatic
    PASSED -> NoInput (output)
    FAILED -> Tester_2
NoInput (output)
Note: Remove detector feature from the stream
Tester_2
    BOOL_OP = OR
    TEST_CLAUSE = TEST _detector_flag ATTRIBUTE_IS_MISSING ""
    TEST_MODE = Automatic
    PASSED -> Output (output)
Output (output)

Bookmark: Create detector feature.
Creator
    GEOMTYPE = Geometry Object
    NUM = 1
    CREATED -> AttributeCreator
AttributeCreator
    ATTR_TABLE = SET_TO _detector_flag = detect
    -> Counter

Bookmark: Make a common counter and calculate the number of features
Counter
    CNT_ATTR = _detector_filter_count
    DOMAIN = DetectroFilter
    SCOPE = Global
    START = 0
    -> StatisticsCalculator
StatisticsCalculator
    COMPUTE_HISTOGRAM = NO
    NUMERIC_ATTR = _num_count
    PREPEND_ATTR_NAME_CHOICE = For multiple results only
    STATS_ATTRS = _detector_filter_count
    COMPLETE -> Tester
